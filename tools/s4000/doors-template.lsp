; PREMIUM S4000 native door controls, v__VERSION__, 2026-09-10.
; Codex / GPT-6 Astra. Only the seven declared door-mounted blocks move.
(setq sd4:groups '__GROUPS__)
(defun sd4:objects (names / ss i e result)
 (setq ss (ssget "_X" '((0 . "INSERT"))) i 0 result nil)
 (if ss (repeat (sslength ss)
  (setq e (ssname ss i) i (1+ i))
  (if (member (cdr (assoc 2 (entget e))) names) (setq result (cons e result))))) result)
(defun sd4:valid (/ g ok)
 (setq ok (= (getvar "INSUNITS") 4))
 (foreach g sd4:groups
  (if (/= (length (sd4:objects (nth 3 g))) (length (nth 3 g))) (setq ok nil))) ok)
(defun sd4:angle (a)
 (while (> a pi) (setq a (- a (* 2 pi))))
 (while (< a (- pi)) (setq a (+ a (* 2 pi)))) a)
(defun sd4:rotate (entity pivot delta / data point x y next angle)
 (setq data (entget entity) point (cdr (assoc 10 data))
       x (- (car point) (car pivot)) y (- (cadr point) (cadr pivot))
       next (list (+ (car pivot) (- (* x (cos delta)) (* y (sin delta))))
                  (+ (cadr pivot) (+ (* x (sin delta)) (* y (cos delta))))
                  (caddr point))
       angle (+ (cdr (assoc 50 data)) delta))
 (entmod (subst (cons 50 angle) (assoc 50 data)
           (subst (cons 10 next) (assoc 10 data) data))) (entupd entity))
(defun sd4:set (which opened / g obj delta goal)
 (foreach g sd4:groups
  (if (or (= which "all") (= which (car g)))
   (progn
    (setq goal (if opened (* pi (/ (nth 2 g) 180.0)) 0.0))
    (foreach obj (sd4:objects (nth 3 g))
     (setq delta (- goal (sd4:angle (cdr (assoc 50 (entget obj))))))
     (if (> (abs delta) 0.00000001) (sd4:rotate obj (nth 1 g) delta)))))))
(defun sd4:run (which opened / olderr)
 (if (sd4:valid)
  (progn
   (setq olderr *error*)
   (defun *error* (msg)
    (command-s "_.UNDO" "_END") (setq *error* olderr)
    (if msg (princ msg)) (princ))
   (command "_.UNDO" "_BEGIN") (sd4:set which opened)
   (command "_.REGEN") (command "_.UNDO" "_END") (setq *error* olderr))
  (princ "Open the S4000 opening drawing in millimetres first.")) (princ))
(defun c:S4000OPEN () (sd4:run "all" T))
(defun c:S4000CLOSE () (sd4:run "all" nil))
(defun c:S4000DOOROPEN () (sd4:run "boiler" T))
(defun c:S4000DOORCLOSE () (sd4:run "boiler" nil))
(defun c:S4000CABINETOPEN () (sd4:run "cabinet" T))
(defun c:S4000CABINETCLOSE () (sd4:run "cabinet" nil))
(defun c:S4000DOORVIEW () (command "_.-VIEW" "_R" "S4000_DOOR") (princ))
(defun c:S4000CABINETVIEW () (command "_.-VIEW" "_R" "S4000_CABINET") (princ))
(defun c:S4000PANEL (/ file dialog result)
 (setq file (strcat (getvar "DWGPREFIX") "S4000-doors.dcl") dialog (load_dialog file))
 (if (> dialog 0)
  (progn (setq result 1)
   (while (> result 0)
    (if (new_dialog "s4000_doors" dialog)
     (progn
      (action_tile "co" "(done_dialog 1)") (action_tile "cc" "(done_dialog 2)")
      (action_tile "bo" "(done_dialog 3)") (action_tile "bc" "(done_dialog 4)")
      (action_tile "allopen" "(done_dialog 5)") (action_tile "allclose" "(done_dialog 6)")
      (action_tile "cv" "(done_dialog 7)") (action_tile "bv" "(done_dialog 8)")
      (action_tile "av" "(done_dialog 9)") (action_tile "dv" "(done_dialog 10)")
      (action_tile "options" "(done_dialog 11)") (setq result (start_dialog))
      (cond ((= result 1) (c:S4000CABINETOPEN)) ((= result 2) (c:S4000CABINETCLOSE))
            ((= result 3) (c:S4000DOOROPEN)) ((= result 4) (c:S4000DOORCLOSE))
            ((= result 5) (c:S4000OPEN)) ((= result 6) (c:S4000CLOSE))
            ((= result 7) (c:S4000CABINETVIEW)) ((= result 8) (c:S4000DOORVIEW))
            ((= result 9) (c:S4000VIEW)) ((= result 10) (c:S4000DAVIEW))
            ((= result 11) (c:S4000OPTIONS)))) (setq result 0)))
   (unload_dialog dialog)) (princ "Keep S4000-doors.dcl next to the DWG.")) (princ))
(princ "S4000 v__VERSION__: S4000PANEL / S4000OPEN / S4000CLOSE / S4000OPTIONS") (princ)

; PREMIUM S3000 opening commands, 2026-09-09, v2026.09.09.5.
; Codex / GPT-6 Astra. Moves only the explicitly named exported blocks.
(defun s3:objects (names / ss i e result)
  (setq ss (ssget "_X" '((0 . "INSERT"))) result nil i 0)
  (if ss (repeat (sslength ss)
    (setq e (ssname ss i) i (1+ i))
    (if (member (cdr (assoc 2 (entget e))) names)
      (setq result (cons e result)))))
  result)
(defun s3:angle (a)
  (while (> a pi) (setq a (- a (* 2 pi))))
  (while (< a (- pi)) (setq a (+ a (* 2 pi)))) a)
(defun s3:valid ()
  (and (= (getvar "INSUNITS") 4)
       (= (length (s3:objects '("S3000_boiler_door"))) 1)
       (= (length (s3:objects '("S3000_cabinet_door"))) 1)))
(defun s3:rotate (entity pivot delta / data point x y next angle)
  (setq data (entget entity) point (cdr (assoc 10 data))
        x (- (car point) (car pivot)) y (- (cadr point) (cadr pivot))
        next (list (+ (car pivot) (- (* x (cos delta)) (* y (sin delta))))
                   (+ (cadr pivot) (+ (* x (sin delta)) (* y (cos delta))))
                   (caddr point))
        angle (+ (cdr (assoc 50 data)) delta))
  (entmod (subst (cons 50 angle) (assoc 50 data)
            (subst (cons 10 next) (assoc 10 data) data)))
  (entupd entity))
(defun s3:set (which opened / names pivot degrees main delta obj)
  (if (= which "cabinet")
    (setq names '("S3000_cabinet_door" "S3000_lc220" "S3000_lc440" "S3000_bc970")
          pivot '(-1225.0 -363.0 1500.0) degrees -110.0)
    (setq names '("S3000_boiler_door" "S3000_burner")
          pivot '(-848.0 -1685.0 1060.0) degrees -105.0))
  (setq main (car (s3:objects (list (car names)))))
  (if main (progn
    (setq delta (- (if opened (* pi (/ degrees 180.0)) 0.0)
                   (s3:angle (cdr (assoc 50 (entget main))))))
    (if (> (abs delta) 0.00000001)
      (foreach obj (s3:objects names) (s3:rotate obj pivot delta))))))
(defun s3:run (which opened / olderr)
  (if (s3:valid)
    (progn
      (setq olderr *error*)
      (defun *error* (msg)
        (command-s "_.UNDO" "_END") (setq *error* olderr)
        (if msg (princ msg)) (princ))
      (command "_.UNDO" "_BEGIN")
      (if (member which '("all" "cabinet")) (s3:set "cabinet" opened))
      (if (member which '("all" "boiler")) (s3:set "boiler" opened))
      (command "_.REGEN") (command "_.UNDO" "_END") (setq *error* olderr))
    (princ "Open the S3000 v2026.09.09.5 drawing in millimetres first."))
  (princ))
(defun c:S3000OPEN () (s3:run "all" T))
(defun c:S3000CLOSE () (s3:run "all" nil))
(defun c:S3000CABINETOPEN () (s3:run "cabinet" T))
(defun c:S3000CABINETCLOSE () (s3:run "cabinet" nil))
(defun c:S3000DOOROPEN () (s3:run "boiler" T))
(defun c:S3000DOORCLOSE () (s3:run "boiler" nil))
(defun s3:view (name direction target height / data)
  (if (s3:valid) (progn
    (if (tblsearch "VIEW" name) (command "_.-VIEW" "_D" name))
    (setq data (list '(0 . "VIEW") '(100 . "AcDbSymbolTableRecord")
      '(100 . "AcDbViewTableRecord") (cons 2 name) '(70 . 0)
      (cons 40 height) (cons 41 (* height 1.6)) '(10 0.0 0.0)
      (cons 11 direction) (cons 12 target) '(42 . 50.0)
      '(43 . 0.0) '(44 . 0.0) '(50 . 0.0) '(71 . 0)))
    (entmake data)
    (command "_.-VIEW" "_R" name)
    (if (tblsearch "LAYER" "S3000_49_deaerator")
      (command "_.-LAYER" "_F" "S3000_49_deaerator" ""))
    (command "_.REGEN")))
  (princ))
(defun c:S3000CABINETVIEW ()
  (s3:view "S3000_INSIDE_CABINET" '(-1.0 -0.45 0.23) '(-1270.0 -220.0 1500.0) 1150.0))
(defun c:S3000DOORVIEW ()
  (s3:view "S3000_INSIDE_BOILER" '(0.45 -1.0 0.22) '(-150.0 -1300.0 1100.0) 3200.0))
(defun c:S3000ECOVIEW ()
  (s3:view "S3000_SPACER_500" '(-1.0 0.45 0.30) '(0.0 1800.0 1100.0) 2600.0))
(defun c:S3000ALLVIEW ()
  (if (and (s3:valid) (tblsearch "VIEW" "S3000_ALL_ISO"))
    (command "_.-VIEW" "_R" "S3000_ALL_ISO")) (princ))
(defun c:S3000PANEL (/ file dialog result)
  (setq file (if (boundp 's3:directory)
               (strcat s3:directory "/S3000-doors.dcl")
               (strcat (getvar "DWGPREFIX") "S3000-doors.dcl")))
  (setq dialog (load_dialog file))
  (if (> dialog 0)
    (progn
      (setq result 1)
      (while (> result 0)
        (if (new_dialog "s3000" dialog)
          (progn
            (action_tile "co" "(done_dialog 1)")
            (action_tile "cc" "(done_dialog 2)")
            (action_tile "bo" "(done_dialog 3)")
            (action_tile "bc" "(done_dialog 4)")
            (action_tile "allopen" "(done_dialog 5)")
            (action_tile "allclose" "(done_dialog 6)")
            (action_tile "cv" "(done_dialog 7)")
            (action_tile "bv" "(done_dialog 8)")
            (action_tile "av" "(done_dialog 9)")
            (action_tile "ev" "(done_dialog 10)")
            (setq result (start_dialog))
            (cond ((= result 1) (s3:run "cabinet" T))
                  ((= result 2) (s3:run "cabinet" nil))
                  ((= result 3) (s3:run "boiler" T))
                  ((= result 4) (s3:run "boiler" nil))
                  ((= result 5) (s3:run "all" T))
                  ((= result 6) (s3:run "all" nil))
                  ((= result 7) (c:S3000CABINETVIEW))
                  ((= result 8) (c:S3000DOORVIEW))
                  ((= result 9) (c:S3000ALLVIEW))
                  ((= result 10) (c:S3000ECOVIEW))))
          (setq result 0)))
      (unload_dialog dialog))
    (princ "Keep S3000-doors.dcl next to the DWG."))
  (princ))
(princ "S3000: S3000PANEL / S3000OPEN / S3000CLOSE")
(princ)

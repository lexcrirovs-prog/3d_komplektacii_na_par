; PREMIUM S-4000 / Comfort / 8-12 bar / v2026.09.10.1 / Codex GPT-6 Astra
; Changes only S4000 component-layer visibility. State is stored in this DWG.
(setq s4:rules '(
__RULES__
))
(setq s4:defaults '__DEFAULT__)
(defun s4:read (/ data)
 (setq data (dictsearch (namedobjdict) "S4000_STATE"))
 (if data (read (cdr (assoc 1 data))) s4:defaults))
(defun s4:write (state / data en)
 (setq data (dictsearch (namedobjdict) "S4000_STATE"))
 ; AutoCAD 2027 appends XRECORD payload on entmod. Replace only our own record.
 (if data
  (progn (dictremove (namedobjdict) "S4000_STATE") (entdel (cdr (assoc -1 data)))))
 (setq en (entmakex (list '(0 . "XRECORD") '(100 . "AcDbXrecord") '(280 . 1) (cons 1 (vl-prin1-to-string state)))))
 (dictadd (namedobjdict) "S4000_STATE" en) state)
(defun s4:set (state key value) (subst (cons key value) (assoc key state) state))
(defun s4:apply (state / rule test shown en data flags)
 (foreach rule s4:rules
  (setq shown T)
  (foreach test (cdr rule) (if (/= (cdr (assoc (car test) state)) (cdr test)) (setq shown nil)))
  (if (setq en (tblobjname "LAYER" (car rule)))
   (progn (setq data (entget en) flags (cdr (assoc 70 data)))
    (entmod (subst (cons 70 (if shown (logand flags -2) (logior flags 1))) (assoc 70 data) data)))))
 (s4:write state) (command "_.REGEN") (princ))
(defun s4:toggle (key value) (s4:apply (s4:set (s4:read) key value)))
(defun c:S4000OPTIONS (/ dialog result key)
 (setq dialog (load_dialog (strcat (getvar "DWGPREFIX") "S4000-options.dcl")))
 (if (and (> dialog 0) (new_dialog "s4000_options" dialog))
  (progn (setq s4:pending (s4:read))
   (foreach key '("economizer" "deaerator" "modulation" "gpz" "bdv" "fv")
    (set_tile key (itoa (cdr (assoc key s4:pending)))))
   (action_tile "economizer" "(setq s4:pending (s4:set s4:pending \"economizer\" (atoi $value)))")
   (action_tile "deaerator" "(setq s4:pending (s4:set s4:pending \"deaerator\" (atoi $value)))")
   (action_tile "modulation" "(setq s4:pending (s4:set s4:pending \"modulation\" (atoi $value)))")
   (action_tile "gpz" "(setq s4:pending (s4:set s4:pending \"gpz\" (atoi $value)))")
   (action_tile "bdv" "(setq s4:pending (s4:set s4:pending \"bdv\" (atoi $value)))")
   (action_tile "fv" "(setq s4:pending (s4:set s4:pending \"fv\" (atoi $value)))")
   (action_tile "accept" "(done_dialog 1)")
   (action_tile "cancel" "(done_dialog 0)")
   (setq result (start_dialog)) (unload_dialog dialog)
   (if (= result 1) (s4:apply s4:pending)))
  (princ "\nKeep S4000-options.dcl next to the DWG.")) (princ))
(defun c:S4000ALL () (s4:apply s4:defaults))
(defun c:S4000BASE () (s4:apply '(("economizer" . 0) ("deaerator" . 0) ("modulation" . 0) ("gpz" . 0) ("bdv" . 0) ("fv" . 0))))
(defun c:S4000ECOON () (s4:toggle "economizer" 1))
(defun c:S4000ECOOFF () (s4:toggle "economizer" 0))
(defun c:S4000MODON () (s4:toggle "modulation" 1))
(defun c:S4000MODOFF () (s4:toggle "modulation" 0))
(defun c:S4000GPZON () (s4:toggle "gpz" 1))
(defun c:S4000GPZOFF () (s4:toggle "gpz" 0))
(defun c:S4000DAON () (s4:toggle "deaerator" 1))
(defun c:S4000DAOFF () (s4:toggle "deaerator" 0))
(defun c:S4000VIEW () (command "_.-VIEW" "_R" "S4000_ALL") (princ))
(defun c:S4000REAR () (command "_.-VIEW" "_R" "S4000_REAR") (princ))
(defun c:S4000PUMPS () (command "_.-VIEW" "_R" "S4000_PUMPS") (princ))
(defun c:S4000DAVIEW () (command "_.-VIEW" "_R" "S4000_DEAERATOR") (princ))
(princ "\nS-4000 Comfort v2026.09.10.1: S4000OPTIONS / S4000VIEW / S4000REAR")
(princ)
